FME workspace cw9.fmw

Parameters:
- DestDataset_GEODATABASE_FILE_3 = Results   # File Geodatabase
- SourceDataset_TIFF_3 = ""$(FME_MF_DIR)ras250_gb\ras250_gb\data\HP.tif" "$(FME_MF_DIR)ras250_gb\ras250_gb\data\HT.tif" "$(FME_MF_DIR)ras250_gb\ras250_gb\data\HU.tif" "$(FME_MF_DIR)ras250_gb\ras250_gb\data\HW.tif" "$(FME_MF_DIR)ras250_gb\ras250_gb\data\HX.tif" "$(FME_MF_DIR)ras250_gb\ras250_gb\data\HY.tif" "$(FME_MF_DIR)ras250_gb\ras250_gb\data\HZ.tif" "$(FME_MF_DIR)ras250_gb\ras250_gb\data\NA.tif" "$(FME_MF_DIR)ras250_gb\ras250_gb\data\NB.tif" "$(FME_MF_DIR)ras250_gb\ras250_gb\data\NC.tif" "$(FME_MF_DIR)ras250_gb\ras250_gb\data\ND.tif" "$(FME_MF_DIR)ras250_gb\ras250_gb\data\NF.tif" "$(FME_MF_DIR)ras250_gb\ras250_gb\data\NG.tif" "$(FME_MF_DIR)ras250_gb\ras250_gb\data\NH.tif" "$(FME_MF_DIR)ras250_gb\ras250_gb\data\NJ.tif" "$(FME_MF_DIR)ras250_gb\ras250_gb\data\NK.tif" "$(FME_MF_DIR)ras250_gb\ras250_gb\data\NL.tif" "$(FME_MF_DIR)ras250_gb\ras250_gb\data\NM.tif" "$(FME_MF_DIR)ras250_gb\ras250_gb\data\NN.tif" "$(FME_MF_DIR)ras250_gb\ras250_gb\data\NO.tif" "$(FME_MF_DIR)ras250_gb\ras250_gb\data\NR.tif" "$(FME_MF_DIR)ras250_gb\ras250_gb\data\NS.tif" "$(FME_MF_DIR)ras250_gb\ras250_gb\data\NT.tif" "$(FME_MF_DIR)ras250_gb\ras250_gb\data\NU.tif" "$(FME_MF_DIR)ras250_gb\ras250_gb\data\NW.tif" "$(FME_MF_DIR)ras250_gb\ras250_gb\data\NX.tif" "$(FME_MF_DIR)ras250_gb\ras250_gb\data\NY.tif" "$(FME_MF_DIR)ras250_gb\ras250_gb\data\NZ.tif" "$(FME_MF_DIR)ras250_gb\ras250_gb\data\OV.tif" "$(FME_MF_DIR)ras250_gb\ras250_gb\data\SC.tif" "$(FME_MF_DIR)ras250_gb\ras250_gb\data\SD.tif" "$(FME_MF_DIR)ras250_gb\ras250_gb\data\SE.tif" "$(FME_MF_DIR)ras250_gb\ras250_gb\data\SH.tif" "$(FME_MF_DIR)ras250_gb\ras250_gb\data\SJ.tif" "$(FME_MF_DIR)ras250_gb\ras250_gb\data\SK.tif" "$(FME_MF_DIR)ras250_gb\ras250_gb\data\SM.tif" "$(FME_MF_DIR)ras250_gb\ras250_gb\data\SN.tif" "$(FME_MF_DIR)ras250_gb\ras250_gb\data\SO.tif" "$(FME_MF_DIR)ras250_gb\ras250_gb\data\SP.tif" "$(FME_MF_DIR)ras250_gb\ras250_gb\data\SR.tif" "$(FME_MF_DIR)ras250_gb\ras250_gb\data\SS.tif" "$(FME_MF_DIR)ras250_gb\ras250_gb\data\ST.tif" "$(FME_MF_DIR)ras250_gb\ras250_gb\data\SU.tif" "$(FME_MF_DIR)ras250_gb\ras250_gb\data\SV.tif" "$(FME_MF_DIR)ras250_gb\ras250_gb\data\SW.tif" "$(FME_MF_DIR)ras250_gb\ras250_gb\data\SX.tif" "$(FME_MF_DIR)ras250_gb\ras250_gb\data\SY.tif" "$(FME_MF_DIR)ras250_gb\ras250_gb\data\SZ.tif" "$(FME_MF_DIR)ras250_gb\ras250_gb\data\TA.tif" "$(FME_MF_DIR)ras250_gb\ras250_gb\data\TF.tif" "$(FME_MF_DIR)ras250_gb\ras250_gb\data\TG.tif" "$(FME_MF_DIR)ras250_gb\ras250_gb\data\TL.tif" "$(FME_MF_DIR)ras250_gb\ras250_gb\data\TM.tif" "$(FME_MF_DIR)ras250_gb\ras250_gb\data\TQ.tif" "$(FME_MF_DIR)ras250_gb\ras250_gb\data\TR.tif" "$(FME_MF_DIR)ras250_gb\ras250_gb\data\TV.tif""   # Source TIFF (Tagged Image File Format) File(s)
- SourceDataset_SHAPEFILE = $(FME_MF_DIR)bdline_essh_gb\Data\GB\scotland_and_wales_region.shp   # Source Esri Shapefile(s)
- DestDataset_POSTGIS = postgis   # Connection
- DestDataset_POSTGIS_3 = postgis   # Connection

Readers:
- TIFF_1: TIFF from $(SourceDataset_TIFF_3)
- SHAPEFILE_1: SHAPEFILE from $(SourceDataset_SHAPEFILE)

Writers:
- GEODATABASE_FILE_1: GEODATABASE_FILE to $(DestDataset_GEODATABASE_FILE_3) in OSGB-GPS-2015-OSTN15
- POSTGIS_1: POSTGIS to $(DestDataset_POSTGIS)
- POSTGIS_2: POSTGIS to $(DestDataset_POSTGIS_3)

scotland_and_wales_region (reader SHAPEFILE_1)
    attributes: NAME char(100), AREA_CODE char(3), DESCRIPTIO char(50), FILE_NAME char(100), NUMBER number(11,0), NUMBER0 number(11,0), POLYGON_ID number(11,0), UNIT_ID number(11,0), CODE char(9), HECTARES float, AREA float, TYPE_CODE char(2), DESCRIPT0 char(25), TYPE_COD0 char(3), DESCRIPT1 char(36)
    -> Tester
Tester
    BOOL_OP = OR
    COMPOSITE_TEST = 1 OR 2 OR 3
    TEST_CLAUSE:
      TEST @Value(FILE_NAME) = SOUTH_WALES_EAST_ASSEMBLY_ER
      TEST @Value(FILE_NAME) = SOUTH_WALES_CENTRAL_ASSEMBLY_ER
      TEST @Value(FILE_NAME) = SOUTH_WALES_WEST_ASSEMBLY_ER
    TEST_MODE = TEST
    PASSED -> SpatialFilter [Filter]
    PASSED -> Dissolver
Dissolver
    ACCUM_INPUT_ATTRS = Use Attributes From One Feature
    CLEANING_TOLERANCE = Automatic
    CONNECT_Z_MODE = First Wins
    DEAGGREGATE_INPUT = Yes
    AREA -> Clipper [CLIPPER]
TIFF (reader TIFF_1)
    -> Reprojector
    -> SpatialFilter [Candidate]
Reprojector
    DEST = OSGB-GPS-2015-OSTN15
    INTERPOLATION_TYPE_NAME = Nearest Neighbor
    RASTER_CELL_SIZE = Preserve Cells
    RASTER_TOLERANCE = 0.0
    SOURCE = Read from feature
    REPROJECTED -> RasterExtentsCoercer
RasterExtentsCoercer
    EXTENTS_TYPE = Raster Extents
    EXTENTS -> FilePropertyExtractor
FilePropertyExtractor
    FMT = FME Date/Time (%Y%m%d%H%M%S)
    PATH = @Value(fme_dataset)
    -> AttributeCreator
AttributeCreator
    ATTR_TABLE = SET_TO NewName = @Value(fme_basename)_@Value(_file_size)
    -> Extents (writer GEODATABASE_FILE_1)
Extents (writer GEODATABASE_FILE_1)
    attributes: NewName char(200)
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CLIPPEE]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterMosaicker
    INSIDE -> Exports (writer POSTGIS_2)
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> Exports_scalone (writer POSTGIS_1)
Exports_scalone (writer POSTGIS_1)
Exports (writer POSTGIS_2)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
